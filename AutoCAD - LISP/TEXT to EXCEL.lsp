(defun LM:csv-addquotes ( str sep / pos )
	(cond
		( (wcmatch str (strcat "*[`" sep "\"]*"))
			(setq pos 0)
			(while (setq pos (vl-string-position 34 str pos))
				(setq str (vl-string-subst "\"\"" "\"" str pos)
					pos (+ pos 2)
				)
			)
			(strcat "\"" str "\"")
		)
		( str )
	)
)
(defun LM:lst->csv ( lst sep )
	(if (cdr lst)
		(strcat (LM:csv-addquotes (car lst) sep) sep (LM:lst->csv (cdr lst) sep))
		(LM:csv-addquotes (car lst) sep)
	)
)
(defun LM:writecsv ( lst csv / des sep )
	(if (setq des (open csv "w"))
		(progn
			(setq sep (cond ((vl-registry-read "HKEY_CURRENT_USER\\Control Panel\\International" "sList")) (",")))
			(foreach row lst (write-line (LM:lst->csv row sep) des))
			(close des)
			t
		)
	)
)
(defun C:ttx(/ lst ss i el x fn)
	(princ "************* ttx >> text-to-excel")
	(setq lst (list) ss (ssget (list (cons 0 "TEXT"))) )
	(if ss
		(progn
			(repeat (setq i (sslength ss))
				(setq x (ssname ss (setq i (1- i))))
				(setq el (entget x))
				(if (= (cdr (assoc 0 el)) "TEXT")
					(setq lst (append lst (list (list (cdr (assoc 1 el))))))
				)
			)
			(setq fn (vl-filename-mktemp nil nil ".csv"))
			(if (and lst (LM:WriteCSV (reverse lst) fn))
				(startapp "explorer" fn)
			)
		)
	)
	(princ)
)
